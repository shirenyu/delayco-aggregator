module delaycollector-config {

    yang-version 1;
    namespace "urn:opendaylight:packet:delaycollector-config";
    prefix "delaycollector-config";

    description
        "This module contains the base configuration for 
        implementation.";

    revision 2014-05-28 {
        description "Initial revision.";
    }

    container delaycollector-config {
        leaf option-type {
            type uint8;
            default 68;
        }        
        leaf querry-delay {
            type uint8;
            default 1;
        }
        leaf influxdb-address {
            type string;
        }
        leaf is-active{
            type boolean;
            default false;
        }
        leaf influxdb-database-name{
            type string;
        }
        leaf influxdb-measurement-name{
            type string;
        }
    }
}
