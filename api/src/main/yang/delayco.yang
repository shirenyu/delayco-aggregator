module delayco {
    yang-version 1;
    namespace "urn:opendaylight:params:xml:ns:yang:delayco";
    prefix "delayco";

    revision "2015-01-05" {
        description "Initial revision of delayco model";
    }

    rpc getDelay {
        input {
            leaf NodeConnector {
                type string;
            }
        }
        output {
            leaf delay {
                type uint32;
            }
        }
    }
    rpc getGlobalDelay {
        output {
            list delay-list {
                description "latency info";
                config false;
                key "nodeConnector";
                leaf nodeConnector {
                    description "srcnode";
                    type string;
                }
                leaf delay {
                    description "delay";
                    type uint32;
                }
            }
        }
    }
}
